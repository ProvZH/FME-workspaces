FME workspace ov_lijnen.fmw
Title: OV-lijnen in de provincie Zuid-Holland
Description: Deze workspace leest OV-lijnen in van de NDOV via de gtfs-feed van OVapi.  
Deze gegevens worden gefilterd op de provinciegrens.  
Per type openbaar vervoer (bus, tram, metro, ...) worden de gegevens in een CSV-bestand weggeschreven.   
Het CSV-bestand bevat de geometrie in Well-Known Text (WKT) formaat in WGS 84 (EPSG: 4326).
History: ,14-11-2018,Willy Tadema,

Parameters:
- SourceDataset_GTFS = http://gtfs.ovapi.nl/nl/gtfs-nl.zip   # Source GTFS File(s)
- DestDataset_CSV = .\OV.zip   # Destination CSV (Comma Separated Value) Folder
- Provincie = Zuid-Holland
- SourceDataset_WFS = https://geodata.nationaalgeoregister.nl/bestuurlijkegrenzen/wfs?   # Source WFS (Web Feature Service) URL

Readers:
- WFS_1: WFS from $(SourceDataset_WFS) in EPSG:28992
- GTFS_1: GTFS from $(SourceDataset_GTFS)

Writers:
- CSV2_1: CSV2 to $(DestDataset_CSV)

Note: Bestuurlijke grens Zuid-Holland
Note: Zie https://developers.google.com/transit/gtfs/
provincies (reader WFS_1)
    attributes: gml_parent_id xml_buffer, gml_parent_property xml_buffer, gml_id xml_buffer, gid xml_int32, gid.xsi_nil xml_boolean, provincienaam xml_buffer, provincienaam.xsi_nil xml_boolean, geom xml_geometry
    -> SpatialFilter [Filter]
Reprojector
    DEST = EPSG:28992
    INTERPOLATION_TYPE_NAME = Nearest Neighbor
    RASTER_CELL_SIZE = Preserve Cells
    RASTER_TOLERANCE = 0.0
    SOURCE = Read from feature
    REPROJECTED -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> CoordinateRounder
CoordinateRounder
    XPREC = 0
    YPREC = 0
    ZPREC = 0
    ROUNDED -> InlineQuerier [shapes]
InlineQuerier
    QUERY_DEF:
      OV,SELECT s."fme_feature_content", a."agency_name",
             r.route_short_name, r.route_long_name,
             CASE r.route_type
                 WHEN 0
                     THEN 'Tram, Streetcar, Light rail'
                 WHEN 1
                     THEN 'Subway, Metro'
                 WHEN 2
                     THEN 'Rail'
                 WHEN 3
                     THEN 'Bus'
                 WHEN 4
                     THEN 'Ferry'
                 WHEN 5
                     THEN 'Cable car'
                 WHEN 6
                     THEN 'Gondola, Suspended cable car'
                 WHEN 7
                     THEN 'Funicular'
                 ELSE 'Unknown'
             END route_type
      FROM shapes s, trips t, routes r, agency a
      WHERE t.shape_id = s.shape_id AND
            t.route_id = r.route_id AND
            r.agency_id = a.agency_id,FIRST
    QUERY_SCHEMA = OV,shapes.fme_feature_content,fme_feature_content,agency_name,text,route_short_name,text,route_long_name,text,route_type,
    TABLE_DEF = shapes,shape_id,integer,trips,route_id,integer,trip_id,integer,shape_id,integer,routes,route_id,integer,agency_id,integer,route_short_name,text,route_long_name,text,route_type,integer,agency,agency_id,integer,agency_name,text
    OV -> AttributeKeeper
AttributeKeeper
    KEEP_ATTRS = agency_name,route_type,route_long_name,route_short_name
    -> Aggregator
Aggregator
    ACCUM_ATTRS_NAME = Use Attributes From One Feature
    AGGREGATE_TYPE = Homogeneous Collection (If Possible)
    GROUP_BY = route_long_name route_short_name route_type agency_name
    MODE = Geometry - Assemble One Level
    ORDERED = No
    SEP = ,
    AGGREGATE -> GeometryExtractor
GeometryExtractor
    ATTR = geometry
    KIND_LONG = OGC Well Known Text
    OGCVERSION = 1.2
    OGC_WKT_PRECISION_DISPLAY = 64-bit
    PREFER_POLYGON_OVER_SURFACE = No
    REMOVE_GEOMETRY = No
    -> OV (writer CSV2_1)
Note: CSV-bestand per type OV
OV (writer CSV2_1)
    attributes: agency_name string, route_short_name string, route_long_name string, route_type string, geometry string

Bookmark: OpenOV GTFS-feed
shapes (reader GTFS_1)
    attributes: shape_id text
    -> Reprojector
trips (reader GTFS_1)
    attributes: route_id text, service_id text, trip_id text, trip_headsign text, trip_short_name text, direction_id integer, block_id text, shape_id text, wheelchair_accessible integer, bikes_allowed integer
    -> InlineQuerier [trips]
routes (reader GTFS_1)
    attributes: route_id text, agency_id text, route_short_name text, route_long_name text, route_desc text, route_type text, route_url text, route_color text, route_text_color text
    -> InlineQuerier [routes]
agency (reader GTFS_1)
    attributes: agency_id text, agency_name text, agency_url text, agency_timezone text, agency_lang text, agency_phone text, agency_fare_url text
    -> InlineQuerier [agency]
