FME workspace haltebestand.fmw
Startup Python:
      import os, datetime, urllib, gzip, shutil

      filename = 'ExportCHB' + datetime.datetime.now().strftime("%Y%m%d") + '010001.xml.gz'
      url = 'http://data.ndovloket.nl/haltes/' + filename
      temp = os.environ['TEMP']
      zipped = os.path.join(temp, filename)
      unzipped = os.path.join(temp, 'ExportCHB.xml')
      urllib.URLopener().retrieve(url, zipped)

      with gzip.open(zipped, 'rb') as f_in, open(unzipped, 'wb') as f_out:
          shutil.copyfileobj(f_in, f_out)
Shutdown Python:
      import os, datetime

      filename = 'ExportCHB' + datetime.datetime.now().strftime("%Y%m%d") + '010001.xml.gz'
      temp = os.environ['TEMP']
      zipped = os.path.join(temp, filename)
      unzipped = os.path.join(temp, 'ExportCHB.xml')

      os.remove(zipped)
      os.remove(unzipped)

Parameters:
- DestDataset_GEOJSON = .\haltebestand.json   # Destination GeoJSON File
- DestDataset_XLSXW = .\haltebestand.xlsx   # Destination Microsoft Excel File
- SourceDataset_WFS = https://geodata.nationaalgeoregister.nl/bestuurlijkegrenzen/wfs?   # Source WFS (Web Feature Service) URL
- Provincie = Zuid-Holland

Readers:
- WFS_1: WFS from $(SourceDataset_WFS)
- XML_1: XML from ${TEMP}\ExportCHB.xml

Writers:
- GEOJSON_1: GEOJSON to $(DestDataset_GEOJSON) in EPSG:4326
- XLSXW_1: XLSXW to $(DestDataset_XLSXW)

Note: Deze workspace leest de gegevens van haltes in uit het Centraal Halte Bestand. Daarbij wordt gebruikt gemaakt van NDOV Loket van Stichting OpenGeo. / De output bevat twee datasets: / - alle haltes binnen de provincie Zuid-Holland en / - haltes die beheerd worden door de provincie Zuid-Holland (dat zijn er aanzienlijk minder). / Deze workspace is gemaakt met FME Desktop 2016 en werkt binnen de gevirtualiseerde desktop omgeving van de provincie alleen goed in de 64-bit versie van de software!
Note: Centraal Halte Bestand (CHB) wordt in Python startup script gedownload. / Bron: http://data.ndovloket.nl/haltes/
Note: Bronbestand wordt gedownload in startup Python script.
quay (reader XML_1)
    attributes: mutationdate xml_char(21), onlygetout xml_char(6), quayaccessibilityadaptions.alightingpositionwidth xml_decimal(5,2), quayaccessibilityadaptions.bayentranceangles xml_decimal(6,2), quayaccessibilityadaptions.bayexitangles xml_decimal(6,2), quayaccessibilityadaptions.baylength xml_decimal(6,2), quayaccessibilityadaptions.boardingpositionwidth xml_decimal(5,2), quayaccessibilityadaptions.embaymentwidth xml_decimal(5,2), quayaccessibilityadaptions.fulllengthguideline xml_char(6), quayaccessibilityadaptions.groundsurfaceindicator xml_char(6), quayaccessibilityadaptions.guidelines xml_char(6), quayaccessibilityadaptions.guidelinestopplaceconnection xml_char(6), quayaccessibilityadaptions.heightwithenvironment xml_decimal(6,2), quayaccessibilityadaptions.kerbheight xml_decimal(4,2), quayaccessibilityadaptions.lift xml_char(6), quayaccessibilityadaptions.liftedpartlength xml_decimal(6,2), quayaccessibilityadaptions.markedkerb xml_char(6), quayaccessibilityadaptions.mutationdate xml_char(21), quayaccessibilityadaptions.narrowestpassagewidth xml_decimal(5,2), quayaccessibilityadaptions.quayshapetype xml_char(23), quayaccessibilityadaptions.ramp xml_char(6), quayaccessibilityadaptions.ramplength xml_decimal(6,2), quayaccessibilityadaptions.rampwidth xml_decimal(5,2), quayaccessibilityadaptions.stopplaceaccessroute xml_char(6), quayaccessibilityadaptions.tactilegroundsurfaceindicator xml_char(6), quayaccessibilityadaptions.validfrom xml_char(21), quaybearing.compassdirection xml_decimal(4,0), quaybearing.mutationdate xml_char(21), quaybearing.validfrom xml_char(21), quaycode xml_char(14),
      quayconcessionprovider.concessionprovidercode xml_char(5), quayconcessionprovider.mutationdate xml_char(21), quayconcessionprovider.validfrom xml_char(21), quaydisabledaccessible.disabledaccessible xml_char(2), quaydisabledaccessible.mutationdate xml_char(21), quaydisabledaccessible.transportmode xml_char(6), quaydisabledaccessible.validfrom xml_char(21), quaydisabledaccessible{}.disabledaccessible xml_char(2), quaydisabledaccessible{}.mutationdate xml_char(21), quaydisabledaccessible{}.transportmode xml_char(5), quaydisabledaccessible{}.validfrom xml_char(21), quayextraattributes.greenstop xml_char(6), quayextraattributes.hectometersign xml_decimal(8,0), quayextraattributes.liftedbicyclepath xml_char(6), quayextraattributes.mutationdate xml_char(21), quayextraattributes.roadcode xml_char(6), quayextraattributes.validfrom xml_char(21), quayfacilities.audiobutton xml_char(6), quayfacilities.bicycleparking xml_char(6), quayfacilities.bins xml_char(6), quayfacilities.illuminatedstop xml_char(6), quayfacilities.infounit xml_char(6), quayfacilities.leantosupport xml_char(6), quayfacilities.mutationdate xml_char(21), quayfacilities.numberofbicycleplaces xml_decimal(5,0), quayfacilities.ovccharging xml_char(6), quayfacilities.ovccico xml_char(6), quayfacilities.passengerinformationdisplay xml_char(6), quayfacilities.passengerinformationdisplaytype xml_decimal(4,0), quayfacilities.routenetworkmap xml_char(6),
      quayfacilities.seatavailable xml_char(6), quayfacilities.shelter xml_char(6), quayfacilities.shelterpublicity xml_char(6), quayfacilities.stopsign xml_char(6), quayfacilities.stopsigntype xml_char(21), quayfacilities.timetableinformation xml_char(6), quayfacilities.validfrom xml_char(21), quaylocationdata.level xml_decimal(2,0), quaylocationdata.location xml_char(101), quaylocationdata.mutationdate xml_char(21), quaylocationdata.rd-x xml_decimal(7,0), quaylocationdata.rd-y xml_decimal(7,0), quaylocationdata.rd-z xml_decimal(2,0), quaylocationdata.street xml_char(37), quaylocationdata.town xml_char(29), quaylocationdata.validfrom xml_char(21), quaymunicipality.municipalitycode xml_char(10), quaymunicipality.mutationdate xml_char(21), quaymunicipality.validfrom xml_char(21), quaynamedata.mutationdate xml_char(21), quaynamedata.quayname xml_char(36), quaynamedata.stopsidecode xml_char(9), quaynamedata.validfrom xml_char(21), quayowner.mutationdate xml_char(21), quayowner.quayownercode xml_char(11), quayowner.validfrom xml_char(21), quayremarks.mutationdate xml_char(21), quayremarks.remarks xml_char(471), quayremarks.remarkstatus xml_char(8), quayremarks.validfrom xml_char(21),
      quaystatusdata.mutationdate xml_char(21), quaystatusdata.quaystatus xml_char(10), quaystatusdata.validfrom xml_char(21), quaytransportmodes.transportmodedata.mutationdate xml_char(21), quaytransportmodes.transportmodedata.transportmode xml_char(6), quaytransportmodes.transportmodedata.validfrom xml_char(21), quaytransportmodes.transportmodedata{}.mutationdate xml_char(21), quaytransportmodes.transportmodedata{}.transportmode xml_char(5), quaytransportmodes.transportmodedata{}.validfrom xml_char(21), quaytypedata.mutationdate xml_char(21), quaytypedata.quaytype xml_char(17), quaytypedata.validfrom xml_char(21), quayvisuallyaccessible.mutationdate xml_char(21), quayvisuallyaccessible.validfrom xml_char(21), quayvisuallyaccessible.visuallyaccessible xml_char(2), stopinternalcode xml_char(11), stopobjectcode xml_char(11), validfrom xml_char(21), xml_fragment xml_xml, xml_id xml_char(23), xml_matched_element xml_char(5), xml_parent_child_pos xml_char(1), xml_parent_id xml_char(1)
    -> AttributeKeeper
Note: Provinciegrens Zuid-Holland ophalen. / Bron: https://www.pdok.nl/nl/service/wfs-bestuurlijke-grenzen / Met behulp van XML Filter Expression alleen provincie Zuid-Holland selecteren.
provincies (reader WFS_1)
    attributes: gml_parent_id xml_buffer, gml_parent_property xml_buffer, gml_id xml_buffer, gid xml_int32, gid.xsi_nil xml_boolean, provincienaam xml_buffer, provincienaam.xsi_nil xml_boolean, geom xml_geometry
    -> SpatialFilter [Filter]
AttributeRemover
    REMOVE_ATTRS = gid,geom,provincienaam.xsi_nil,gid.xsi_nil,gml_parent_id,gml_id,_predicate,gml_parent_property
    -> Reprojector
Reprojector
    DEST = EPSG:4326
    INTERPOLATION_TYPE_NAME = Nearest Neighbor
    RASTER_CELL_SIZE = Preserve Cells
    RASTER_TOLERANCE = 0.0
    SOURCE = Read from feature
    REPROJECTED -> AttributeCreator
    REPROJECTED -> haltes (writer GEOJSON_1)
haltes (writer GEOJSON_1)
    attributes: provincienaam string, mutationdate string, onlygetout string, quayaccessibilityadaptions.alightingpositionwidth float, quayaccessibilityadaptions.bayentranceangles float, quayaccessibilityadaptions.bayexitangles float, quayaccessibilityadaptions.baylength float, quayaccessibilityadaptions.boardingpositionwidth float, quayaccessibilityadaptions.embaymentwidth float, quayaccessibilityadaptions.fulllengthguideline string, quayaccessibilityadaptions.groundsurfaceindicator string, quayaccessibilityadaptions.guidelines string, quayaccessibilityadaptions.guidelinestopplaceconnection string, quayaccessibilityadaptions.heightwithenvironment float, quayaccessibilityadaptions.kerbheight float, quayaccessibilityadaptions.lift string, quayaccessibilityadaptions.liftedpartlength float, quayaccessibilityadaptions.markedkerb string, quayaccessibilityadaptions.narrowestpassagewidth float, quayaccessibilityadaptions.quayshapetype string, quayaccessibilityadaptions.ramp string, quayaccessibilityadaptions.ramplength float, quayaccessibilityadaptions.rampwidth float, quayaccessibilityadaptions.stopplaceaccessroute string, quayaccessibilityadaptions.tactilegroundsurfaceindicator string, quaybearing.compassdirection int, quaycode string, quayconcessionprovider.concessionprovidercode string, quaydisabledaccessible.disabledaccessible string, quaydisabledaccessible.transportmode string,
      quayextraattributes.greenstop string, quayextraattributes.hectometersign int, quayextraattributes.liftedbicyclepath string, quayextraattributes.roadcode string, quayfacilities.audiobutton string, quayfacilities.bicycleparking string, quayfacilities.bins string, quayfacilities.illuminatedstop string, quayfacilities.infounit string, quayfacilities.leantosupport string, quayfacilities.numberofbicycleplaces int, quayfacilities.ovccharging string, quayfacilities.ovccico string, quayfacilities.passengerinformationdisplay string, quayfacilities.passengerinformationdisplaytype int, quayfacilities.routenetworkmap string, quayfacilities.seatavailable string, quayfacilities.shelter string, quayfacilities.shelterpublicity string, quayfacilities.stopsign string, quayfacilities.stopsigntype string, quayfacilities.timetableinformation string, quaylocationdata.level int, quaylocationdata.location string, quaylocationdata.rd-x int, quaylocationdata.rd-y int, quaylocationdata.rd-z int, quaylocationdata.street string, quaylocationdata.town string, quaymunicipality.municipalitycode string,
      quaynamedata.quayname string, quaynamedata.stopsidecode string, quayowner.quayownercode string, quayremarks.remarks string, quayremarks.remarkstatus string, quaystatusdata.quaystatus string, quaytransportmodes.transportmodedata.transportmode string, quaytypedata.quaytype string, quayvisuallyaccessible.visuallyaccessible string
Note: Gedownload bronbestand (.gz en .XML) wordt opgeruimd in Python shutdown script.
AttributeCreator
    ATTR_TABLE:
      SET_TO lat = @YValue()
      SET_TO lon = @XValue()
    -> Sheet1 (writer XLSXW_1)
Sheet1 (writer XLSXW_1)
    attributes: lat auto(20), lon auto(20), provincienaam string(20), mutationdate string(21), onlygetout string(6), quayaccessibilityadaptions.alightingpositionwidth number(5), quayaccessibilityadaptions.bayentranceangles number(6), quayaccessibilityadaptions.bayexitangles number(6), quayaccessibilityadaptions.baylength number(6), quayaccessibilityadaptions.boardingpositionwidth number(5), quayaccessibilityadaptions.embaymentwidth number(5), quayaccessibilityadaptions.fulllengthguideline string(6), quayaccessibilityadaptions.groundsurfaceindicator string(6), quayaccessibilityadaptions.guidelines string(6), quayaccessibilityadaptions.guidelinestopplaceconnection string(6), quayaccessibilityadaptions.heightwithenvironment number(6), quayaccessibilityadaptions.kerbheight number(4), quayaccessibilityadaptions.lift string(6), quayaccessibilityadaptions.liftedpartlength number(6), quayaccessibilityadaptions.markedkerb string(6), quayaccessibilityadaptions.narrowestpassagewidth number(5), quayaccessibilityadaptions.quayshapetype string(23), quayaccessibilityadaptions.ramp string(6), quayaccessibilityadaptions.ramplength number(6), quayaccessibilityadaptions.rampwidth number(5), quayaccessibilityadaptions.stopplaceaccessroute string(6), quayaccessibilityadaptions.tactilegroundsurfaceindicator string(6), quaybearing.compassdirection number(4), quaycode string(14), quayconcessionprovider.concessionprovidercode string(5),
      quaydisabledaccessible.disabledaccessible string(2), quaydisabledaccessible.transportmode string(6), quayextraattributes.greenstop string(6), quayextraattributes.hectometersign number(8), quayextraattributes.liftedbicyclepath string(6), quayextraattributes.roadcode string(6), quayfacilities.audiobutton string(6), quayfacilities.bicycleparking string(6), quayfacilities.bins string(6), quayfacilities.illuminatedstop string(6), quayfacilities.infounit string(6), quayfacilities.leantosupport string(6), quayfacilities.numberofbicycleplaces number(5), quayfacilities.ovccharging string(6), quayfacilities.ovccico string(6), quayfacilities.passengerinformationdisplay string(6), quayfacilities.passengerinformationdisplaytype number(4), quayfacilities.routenetworkmap string(6), quayfacilities.seatavailable string(6), quayfacilities.shelter string(6), quayfacilities.shelterpublicity string(6), quayfacilities.stopsign string(6), quayfacilities.stopsigntype string(21), quayfacilities.timetableinformation string(6), quaylocationdata.level number(2), quaylocationdata.location string(101), quaylocationdata.rd-x number(7), quaylocationdata.rd-y number(7), quaylocationdata.rd-z number(2), quaylocationdata.street string(37),
      quaylocationdata.town string(29), quaymunicipality.municipalitycode string(10), quaynamedata.quayname string(36), quaynamedata.stopsidecode string(9), quayowner.quayownercode string(11), quayremarks.remarks string(471), quayremarks.remarkstatus string(8), quaystatusdata.quaystatus string(10), quaytransportmodes.transportmodedata.transportmode string(6), quaytypedata.quaytype string(17), quayvisuallyaccessible.visuallyaccessible string(2)

Bookmark: Filter attributen en features
AttributeKeeper
    KEEP_ATTRS = quayaccessibilityadaptions.heightwithenvironment,quaynamedata.quayname,quayfacilities.shelterpublicity,quayaccessibilityadaptions.ramplength,quayfacilities.illuminatedstop,quayaccessibilityadaptions.stopplaceaccessroute,quayaccessibilityadaptions.guidelines,quayaccessibilityadaptions.alightingpositionwidth,quayconcessionprovider.concessionprovidercode,quaylocationdata.street,quaylocationdata.rd-y,quayfacilities.infounit,quayextraattributes.liftedbicyclepath,quayaccessibilityadaptions.boardingpositionwidth,quayaccessibilityadaptions.markedkerb,quayaccessibilityadaptions.ramp,quayfacilities.bicycleparking,quayfacilities.leantosupport,quaylocationdata.location,quaylocationdata.level,quaylocationdata.town,quayfacilities.passengerinformationdisplay,quaytransportmodes.transportmodedata.transportmode,quayfacilities.ovccico,quayfacilities.bins,quayaccessibilityadaptions.quayshapetype,quaynamedata.stopsidecode,quayremarks.remarkstatus,quayowner.quayownercode,quayaccessibilityadaptions.tactilegroundsurfaceindicator,quayaccessibilityadaptions.embaymentwidth,quaystatusdata.quaystatus,quayaccessibilityadaptions.groundsurfaceindicator,mutationdate,onlygetout,quayfacilities.stopsigntype,quayextraattributes.roadcode,quayfacilities.seatavailable,quayaccessibilityadaptions.kerbheight,quayaccessibilityadaptions.baylength,quaydisabledaccessible.disabledaccessible,quayvisuallyaccessible.visuallyaccessible,quayfacilities.passengerinformationdisplaytype,quayremarks.remarks,quayaccessibilityadaptions.fulllengthguideline,quaybearing.compassdirection,quayextraattributes.hectometersign,quayfacilities.stopsign,quayaccessibilityadaptions.narrowestpassagewidth,quaytypedata.quaytype,quayaccessibilityadaptions.bayentranceangles,quaycode,quayfacilities.shelter,quaylocationdata.rd-x,quaylocationdata.rd-z,quayfacilities.timetableinformation,quayfacilities.numberofbicycleplaces,quayfacilities.ovccharging,quayfacilities.audiobutton,quayaccessibilityadaptions.guidelinestopplaceconnection,quayaccessibilityadaptions.lift,quayextraattributes.greenstop,quayaccessibilityadaptions.bayexitangles,quayaccessibilityadaptions.rampwidth,quaydisabledaccessible.transportmode,quaymunicipality.municipalitycode,quayfacilities.routenetworkmap,quayaccessibilityadaptions.liftedpartlength
    -> TestFilter
TestFilter
    DEFAULT_VALUE = Gepland of vervallen
    TEST_LIST:
      BOOL_OP,OR,COMPOSITE_TEST,<Unused>,TEST_CLAUSE,"TEST @Value(quaystatusdata.quaystatus) = available
      TEST @Value(quaystatusdata.quaystatus) = unavailable",Beschikbaar of tijdelijk niet-beschikbaar
    Beschikbaar of tijdelijk niet-beschikbaar -> VertexCreator

Bookmark: Maak geometrie (RD New)
VertexCreator
    MODE_NAME = Add Point
    XVAL = @Value(quaylocationdata.rd-x)
    YVAL = @Value(quaylocationdata.rd-y)
    -> CoordinateSystemSetter
CoordinateSystemSetter
    COORDSYS = EPSG:28992
    -> SpatialFilter [Candidate]

Bookmark: Filter op provinciegrens Groningen
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeRemover
