FME workspace donl2dataplatform.fmw
Title: Kopie van Data.overheid.nl naar Dataplatform.nl
Description: Deze workspace kopieert de metadata van de provincie Zuid-Holland op Data.overheid.nl naar Dataplatform.nl. Hij is bedoeld om de NGR metadata initieel in te lezen in de database van Dataplatform.nl.
Data.overheid.nl en Dataplatform.nl zijn beide gebouwd op CKAN. Voor het uitlezen en wegschrijven van de gegevens maak de workspace dan ook gebruik van de CKAN API. 
Alleen de metadata die via het Nationaal Georegister (NGR) gepubliceerd is, wordt meegenomen in de kopieerslag.
De mapping van het NGR datamodel op dat van CKAN is de reden om de metadata te kopiëren van data.overheid.nl, en níet rechtstreeks van het NGR. Het is lastig om deze mapping te maken. We streven er bovendien naar om de gegevens op Dataplatform.nl zo veel mogelijk aan te laten sluiten op de landelijke metadatastandaarden. Vandaar dat we er voor gekozen hebben om de mapping van data.overheid.nl over te nemen.
Via de published parameter environment kun je switchen tussen de acceptatie- en productieomgeving van Dataplatform.nl. Let op: je moet eerst wel de juiste API keys invullen in de private parameters api_key_acc en api_key_prod.
De published parameter prefix bevat de tekst die bij het kopiëren vooraan de naam van een dataset wordt geplakt. De parameter is standaard leeg. Het kan handig zijn om tijdens testen wél een prefix mee te geven. Je kunt een dataset of package namelijk wel verwijderen, maar hij is pas écht verdwenen na 'purgen' van de database. Om dit te kunnen doen, heb je echter beheerrechten nodig.
History: 5-1-2019,Willy Tadema,Eerste versie - gebruikt om de NGR metadata van provincie Zuid-Holland te kopiëren van data.overheid.nl naar Dataplatform.nl,

Parameters:
- environment = acc   # Omgeving Dataplatform.nl
- prefix =   # Prefix voor package name
- dataplatform_url_prod = https://ckan.dataplatform.nl   # URL Dataplatform API productieomgeving
- dataplatform_url_acc = https://acc-ckan.dataplatform.nl   # https URL Dataplatform API acceptatieomgeving
- dataplatform_url:   # Python Script
      import fme
      
      env = fme.macroValues.get('environment')
      
      if env == 'prod':
          return fme.macroValues.get('dataplatform_url_prod')
      elif env == 'acc':
          return fme.macroValues.get('dataplatform_url_acc')
- api_key_prod =   # Dataplatform API key productieomgeving
- api_key_acc =   # API key acceptatieomgeving
- api_key:   # Python Script
      import fme
      
      env = fme.macroValues.get('environment')
      
      if env == 'prod':
          return fme.macroValues.get('api_key_prod')
      elif env == 'acc':
          return fme.macroValues.get('api_key_acc')
- donl_url_prod = https://data.overheid.nl/data   # https URL data.overheid.nl API productieomgeving

Creator
    GEOMTYPE = Geometry Object
    NUM = 1
    CREATED -> HTTPCaller
Note: Metadata ophalen van data.overheid.nl. / Selecteer alleen datasets die door de provincie Zuid-Holland in het Nationaal Georegister (NGR) gepubliceerd zijn. / Let op: de API retourneert niet meer dan 1.000 datasets per request!
HTTPCaller
    ADDITIONAL_URL_PARAMETERS = q;+publisher:"http://standaarden.overheid.nl/owms/terms/Zuid-Holland" +source_catalog:"https://nationaalgeoregister.nl" rows;1000 start;0 sort;metadata_created asc
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = response
    TARGET_ATTR_ENCODING = auto-detect
    TARGET_URL = $(donl_url_prod)/api/3/action/package_search
    TRANSFER_TIMEOUT_LENGTH = 90
    USE_COOKIES = No
    VERIFY_SSL_CERTIFICATES = No
    -> JSONFragmenter
Note: Per dataset (package) de volgende data uit de respons filteren: / - title / - notes / - license_id / - NGR metadata id / - data.overheid.nl package id
JSONFragmenter
    EXPLODE_FORMAT = JSON
    EXTRACT_ATTR = Yes
    JSON_ATTR = response
    JSON_QUERY = json["result"]["results"][*]
    NEW_ATTRIBUTES = license_id identifier id name notes title
    READ_FROM_FILE = NO
    RECURSIVE = No
    REJECT_EMPTY_LISTS = YES
    FRAGMENTS -> AttributeManager
AttributeManager
    ATTR_TABLE:
      SET_TO notes = @ReplaceRegEx(@Value(notes),\r?\n,
        )

        Voor meer informatie kunt u ook de [metadata in het Nationaal Georegister](@Value(identifier)) raadplegen.
      REMOVE _creation_instance
      REMOVE _headers{}.name
      REMOVE _headers{}.value
      REMOVE _http_status_code
      REMOVE json_type
      REMOVE json_index
      SET_TO ngr_metadata_id = @Substring(@Value(identifier),48,@Evaluate(@StringLength(@Value(identifier))-48))
      REMOVE identifier
      RENAME_SET_VALUE id > donl_package_id
      SET_TO name = $(prefix)@Value(name)
    -> AttributeKeeper
    -> AttributeValueMapper
Note: Mapping van license_id op het schema van Dataplatform.nl
AttributeValueMapper
    DEFAULT_VALUE = notspecified
    DIRECTION = Forward (Source To Destination)
    LUT = http://standaarden.overheid.nl/owms/terms/geslotenlicentie,other-closed,http://standaarden.overheid.nl/owms/terms/geogedeeld,other-open,http://standaarden.overheid.nl/owms/terms/licentieonbekend,notspecified,http://creativecommons.org/publicdomain/mark/1.0/deed.nl,other-pd,http://creativecommons.org/publicdomain/zero/1.0/deed.nl,cc-zero,http://creativecommons.org/licenses/by/4.0/deed.nl,cc-by,http://creativecommons.org/licenses/by-sa/4.0/deed.nl,cc-by-sa
    SRC = license_id
    VAL_ATTR = license_id
    -> JSONTemplater [ROOT]
AttributeKeeper
    KEEP_ATTRS = ngr_metadata_id,response
    -> JSONFragmenter_2
    -> JSONFragmenter_3
    -> JSONFragmenter_4
Note: tags
JSONFragmenter_3
    EXPLODE_FORMAT = JSON
    EXTRACT_ATTR = Yes
    JSON_ATTR = response
    JSON_QUERY = json["tags"][*]
    NEW_ATTRIBUTES = tags_name
    PREF_STRING = tags_
    READ_FROM_FILE = NO
    RECURSIVE = Yes
    REJECT_EMPTY_LISTS = YES
    FRAGMENTS -> JSONTemplater [TAGS]
Note: resources
JSONFragmenter_2
    EXPLODE_FORMAT = JSON
    EXTRACT_ATTR = Yes
    JSON_ATTR = response
    JSON_QUERY = json["resources"][*]
    NEW_ATTRIBUTES = res_description res_format res_name res_url res_created
    PREF_STRING = res_
    READ_FROM_FILE = NO
    RECURSIVE = Yes
    REJECT_EMPTY_LISTS = YES
    FRAGMENTS -> AttributeValueMapper_2
Note: Mapping van format op het schema van Dataplatform.nl
AttributeValueMapper_2
    DIRECTION = Forward (Source To Destination)
    LUT = OGC:WMS,WMS,OGC:WFS,WFS
    SRC = res_description
    VAL_ATTR = res_format
    -> JSONTemplater [RESOURCES]
Note: themes
JSONFragmenter_4
    EXPLODE_FORMAT = JSON
    EXTRACT_ATTR = No
    JSON_ATTR = response
    JSON_QUERY = json["theme"][*]
    READ_FROM_FILE = NO
    REJECT_EMPTY_LISTS = YES
    FRAGMENTS -> AttributeValueMapper_4
Note: Mapping van theme op het schema van Dataplatform.nl
AttributeValueMapper_4
    DIRECTION = Forward (Source To Destination)
    LUT = http://standaarden.overheid.nl/owms/terms/Afval_(thema),Natuur en milieu,http://standaarden.overheid.nl/owms/terms/Arbeidsomstandigheden_(thema),Werk,http://standaarden.overheid.nl/owms/terms/Arbeidsvoorwaarden,Werk,http://standaarden.overheid.nl/owms/terms/Basisonderwijs_(thema),Onderwijs en wetenschap,http://standaarden.overheid.nl/owms/terms/Begroting,Financiën,http://standaarden.overheid.nl/owms/terms/Belasting,Financiën,http://standaarden.overheid.nl/owms/terms/Beroepsonderwijs_(thema),Onderwijs en wetenschap,http://standaarden.overheid.nl/owms/terms/Bestuur,Bestuur,http://standaarden.overheid.nl/owms/terms/Bestuursrecht,Recht,http://standaarden.overheid.nl/owms/terms/Bezwaar_en_klachten,Recht,http://standaarden.overheid.nl/owms/terms/Bodem,Natuur en milieu,http://standaarden.overheid.nl/owms/terms/Bouwen_en_verbouwen,Huisvesting,http://standaarden.overheid.nl/owms/terms/Bouwnijverheid,Economie,http://standaarden.overheid.nl/owms/terms/Burgerlijk_recht,Recht,http://standaarden.overheid.nl/owms/terms/Criminaliteit,Openbare orde en veiligheid,http://standaarden.overheid.nl/owms/terms/Cultuur_(thema),Cultuur en recreatie,http://standaarden.overheid.nl/owms/terms/Cultuur_en_recreatie,Cultuur en recreatie,http://standaarden.overheid.nl/owms/terms/De_Nederlandse_Antillen_en_Aruba,Bestuur,http://standaarden.overheid.nl/owms/terms/Defensie_(thema),Internationaal,http://standaarden.overheid.nl/owms/terms/Dieren_(thema),Economie,http://standaarden.overheid.nl/owms/terms/Economie,Economie,http://standaarden.overheid.nl/owms/terms/Emigratie_(thema),Migratie en integratie,http://standaarden.overheid.nl/owms/terms/Energie,Natuur en milieu,http://standaarden.overheid.nl/owms/terms/Ethiek,Zorg en gezondheid,http://standaarden.overheid.nl/owms/terms/Europese_zaken,Internationaal,http://standaarden.overheid.nl/owms/terms/Financieel_toezicht,Financiën,http://standaarden.overheid.nl/owms/terms/Financien,Financiën,http://standaarden.overheid.nl/owms/terms/Geluid_(thema),Natuur en milieu,http://standaarden.overheid.nl/owms/terms/Gemeenten,Bestuur,http://standaarden.overheid.nl/owms/terms/Geneesmiddelen_en_medische_hulpmiddelen,Zorg en gezondheid,http://standaarden.overheid.nl/owms/terms/Gezin_en_kinderen,Sociale zekerheid,http://standaarden.overheid.nl/owms/terms/Gezondheidsrisico's,Zorg en gezondheid,http://standaarden.overheid.nl/owms/terms/Handel,Economie,http://standaarden.overheid.nl/owms/terms/Hoger_onderwijs_(thema),Onderwijs en wetenschap,http://standaarden.overheid.nl/owms/terms/Huisvesting_(thema),Huisvesting,http://standaarden.overheid.nl/owms/terms/Huren_en_verhuren,Huisvesting,http://standaarden.overheid.nl/owms/terms/ICT,Economie,http://standaarden.overheid.nl/owms/terms/Immigratie_(thema),Migratie en integratie,http://standaarden.overheid.nl/owms/terms/Industrie_(thema),Economie,http://standaarden.overheid.nl/owms/terms/Inkomensbeleid,Financiën,http://standaarden.overheid.nl/owms/terms/Integratie_(thema),Migratie en integratie,http://standaarden.overheid.nl/owms/terms/Internationaal,Internationaal,http://standaarden.overheid.nl/owms/terms/Internationale_samenwerking_(thema),Internationaal ,http://standaarden.overheid.nl/owms/terms/Jongeren_(thema),Sociale zekerheid,http://standaarden.overheid.nl/owms/terms/Jongeren_(thema),Zorg en gezondheid,http://standaarden.overheid.nl/owms/terms/Koninklijk_Huis_(thema),Bestuur,http://standaarden.overheid.nl/owms/terms/Kopen_en_verkopen,Huisvesting,http://standaarden.overheid.nl/owms/terms/Kunst_(thema),Cultuur en recreatie,http://standaarden.overheid.nl/owms/terms/Landbouw_(thema),Economie,http://standaarden.overheid.nl/owms/terms/Levensloop,Werk,http://standaarden.overheid.nl/owms/terms/Lucht,Natuur en milieu,http://standaarden.overheid.nl/owms/terms/Luchtvaart,Verkeer,http://standaarden.overheid.nl/owms/terms/Markttoezicht,Economie,http://standaarden.overheid.nl/owms/terms/Media,Cultuur en recreatie,http://standaarden.overheid.nl/owms/terms/Migratie_en_integratie,Migratie en integratie,http://standaarden.overheid.nl/owms/terms/Militaire_missies,Internationaal,http://standaarden.overheid.nl/owms/terms/Nabestaanden,Sociale zekerheid,http://standaarden.overheid.nl/owms/terms/Natuur-_en_landschapsbeheer,Migratie en integratie,http://standaarden.overheid.nl/owms/terms/Natuur_en_milieu,Natuur en milieu,http://standaarden.overheid.nl/owms/terms/Nederlanderschap_(thema),Nederlanderschap,http://standaarden.overheid.nl/owms/terms/Netwerken,Ruimte en infrastructuur,http://standaarden.overheid.nl/owms/terms/Ondernemen,Economie,http://standaarden.overheid.nl/owms/terms/Onderwijs_en_wetenschap,Onderwijs en wetenschap,http://standaarden.overheid.nl/owms/terms/Onderzoek_en_wetenschap,Onderwijs en wetenschap,http://standaarden.overheid.nl/owms/terms/Ontslag_(thema),Werk,http://standaarden.overheid.nl/owms/terms/Ontwikkelingssamenwerking,Internationaal,http://standaarden.overheid.nl/owms/terms/Openbare_orde_en_veiligheid,Openbare orde en veiligheid,http://standaarden.overheid.nl/owms/terms/Organisatie_en_beleid,Bestuur,http://standaarden.overheid.nl/owms/terms/Organisatie_en_beleid,Cultuur en recreatie,http://standaarden.overheid.nl/owms/terms/Organisatie_en_beleid,Economie,http://standaarden.overheid.nl/owms/terms/Organisatie_en_beleid,Financiën,http://standaarden.overheid.nl/owms/terms/Organisatie_en_beleid,Huisvesting,http://standaarden.overheid.nl/owms/terms/Organisatie_en_beleid,Internationaal,http://standaarden.overheid.nl/owms/terms/Organisatie_en_beleid,Migratie en integratie,http://standaarden.overheid.nl/owms/terms/Organisatie_en_beleid,Natuur en milieu,http://standaarden.overheid.nl/owms/terms/Organisatie_en_beleid,Onderwijs en wetenschap,http://standaarden.overheid.nl/owms/terms/Organisatie_en_beleid,Openbare orde en veiligheid,http://standaarden.overheid.nl/owms/terms/Organisatie_en_beleid,Recht,http://standaarden.overheid.nl/owms/terms/Organisatie_en_beleid,Ruimte en infrastructuur,http://standaarden.overheid.nl/owms/terms/Organisatie_en_beleid,Sociale zekerheid,http://standaarden.overheid.nl/owms/terms/Organisatie_en_beleid,Verkeer,http://standaarden.overheid.nl/owms/terms/Organisatie_en_beleid,Werk,http://standaarden.overheid.nl/owms/terms/Organisatie_en_beleid,Zorg en gezondheid,http://standaarden.overheid.nl/owms/terms/Organisatie_en_beleid,Economie,http://standaarden.overheid.nl/owms/terms/Ouderen,Sociale zekerheid,http://standaarden.overheid.nl/owms/terms/Ouderen,Zorg en gezondheid,http://standaarden.overheid.nl/owms/terms/Overige_economische_sectoren,Economie,http://standaarden.overheid.nl/owms/terms/Overige_vormen_van_onderwijs,Onderwijs en wetenschap,http://standaarden.overheid.nl/owms/terms/Parlement,Bestuur,http://standaarden.overheid.nl/owms/terms/Planten,Economie,http://standaarden.overheid.nl/owms/terms/Politie_brandweer_en_hulpdiensten,Openbare orde en veiligheid,http://standaarden.overheid.nl/owms/terms/Provincies,Bestuur,http://standaarden.overheid.nl/owms/terms/Rampen,Openbare orde en veiligheid,http://standaarden.overheid.nl/owms/terms/Recht_(thema),Recht,http://standaarden.overheid.nl/owms/terms/Rechtspraak,Recht,http://standaarden.overheid.nl/owms/terms/Recreatie_(thema),Cultuur en recreatie,http://standaarden.overheid.nl/owms/terms/Reizen,Internationaal,http://standaarden.overheid.nl/owms/terms/Religie,Cultuur en recreatie,http://standaarden.overheid.nl/owms/terms/Rijksoverheid,Bestuur,http://standaarden.overheid.nl/owms/terms/Ruimte_en_infrastructuur,Ruimte en infrastructuur,http://standaarden.overheid.nl/owms/terms/Ruimtelijke_ordening,Ruimte en infrastructuur,http://standaarden.overheid.nl/owms/terms/Sociale_zekerheid,Sociale zekerheid,http://standaarden.overheid.nl/owms/terms/Spoor,Verkeer,http://standaarden.overheid.nl/owms/terms/Sport_(thema),Cultuur en recreatie,http://standaarden.overheid.nl/owms/terms/Staatsrecht,Recht,http://standaarden.overheid.nl/owms/terms/Staatsveiligheid,Openbare orde en veiligheid,http://standaarden.overheid.nl/owms/terms/Stoffen,Natuur en milieu,http://standaarden.overheid.nl/owms/terms/Strafrecht,Recht,http://standaarden.overheid.nl/owms/terms/Terrorisme_(thema),Openbare orde en veiligheid,http://standaarden.overheid.nl/owms/terms/Tijdelijk_verblijf,Migratie en integratie,http://standaarden.overheid.nl/owms/terms/Toerisme,Economie,http://standaarden.overheid.nl/owms/terms/Transport_(thema),Economie,http://standaarden.overheid.nl/owms/terms/Verkeer_(thema),Verkeer,http://standaarden.overheid.nl/owms/terms/Verzekeringen,Zorg en gezondheid,http://standaarden.overheid.nl/owms/terms/Voeding,Zorg en gezondheid,http://standaarden.overheid.nl/owms/terms/Voedselkwaliteit,Economie,http://standaarden.overheid.nl/owms/terms/Voortgezet_onderwijs_(thema),Onderwijs en wetenschap,http://standaarden.overheid.nl/owms/terms/Water_(verkeer-thema),Natuur en milieu,http://standaarden.overheid.nl/owms/terms/Water_(verkeer-thema),Verkeer,http://standaarden.overheid.nl/owms/terms/Waterkeringen_en_waterbeheer,Ruimte en infrastructuur,http://standaarden.overheid.nl/owms/terms/Waterschappen,Bestuur,http://standaarden.overheid.nl/owms/terms/Weg_(thema),Verkeer,http://standaarden.overheid.nl/owms/terms/Werk_(thema),Werk,http://standaarden.overheid.nl/owms/terms/Werkgelegenheid,Werk,http://standaarden.overheid.nl/owms/terms/Werkloosheid,Sociale zekerheid,http://standaarden.overheid.nl/owms/terms/Ziekte_en_arbeidsongeschiktheid,Sociale zekerheid,http://standaarden.overheid.nl/owms/terms/Ziekten_en_behandelingen,Zorg en gezondheid,http://standaarden.overheid.nl/owms/terms/Zorg_en_gezondheid,Zorg en gezondheid,http://standaarden.overheid.nl/owms/terms/Cultuur_en_recreatie,Cultuur en recreatie,http://standaarden.overheid.nl/owms/terms/Economie,Economie,http://standaarden.overheid.nl/owms/terms/Financien,Financiën,http://standaarden.overheid.nl/owms/terms/Huisvesting_(thema),Huisvesting,http://standaarden.overheid.nl/owms/terms/Internationaal,Internationaal,http://standaarden.overheid.nl/owms/terms/Landbouw_(thema),Landbouw,http://standaarden.overheid.nl/owms/terms/Migratie_en_integratie,Migratie en integratie,http://standaarden.overheid.nl/owms/terms/Natuur_en_milieu,Natuur en milieu,http://standaarden.overheid.nl/owms/terms/Onderwijs_en_wetenschap,Onderwijs en wetenschap
    SRC = response
    VAL_ATTR = theme
    -> TestFilter
    -> AttributeValueMapper_3
Note: group
AttributeValueMapper_3
    DIRECTION = Forward (Source To Destination)
    LUT = Bestuur,bestuur,Cultuur en recreatie,cultuur-en,Economie,economie,Financiën,financien,Huisvesting,huisvesting,Internationaal,,Landbouw,landbouw,Migratie en integratie,migratie-en-integratie,Natuur en milieu,natuur-en-milieu,Onderwijs en wetenschap,onderwijs-en-wetenschap,Openbare orde en veiligheid,openbare,Recht,recht,Ruimte en infrastructuur,ruimte-en-infrastructuur,Sociale zekerheid,sociale-zekerheid,Verkeer,verkeer,Werk,werk,Zorg en gezondheid,zorg-en-gezondheid
    SRC = theme
    VAL_ATTR = group
    -> JSONTemplater [GROUP] [off]
Note: Bij meerdere thema's voor hetzelfde package alleen de eerste selecteren, want Dataplatform.nl kan maar één thema aan
Note: Helaas heeft de gebruiker gekoppeld aan de api key onvoldoende rechten om een package aan een group te koppelen. / Vandaar dat dat dit deel van het script is uitgeschakeld.
TestFilter
    DEFAULT_VALUE = <UNFILTERED>
    TEST_LIST = "BOOL_OP,OR,COMPOSITE_TEST,""""""<Unused>"""""",TEST_CLAUSE,TEST @Value(json_index) = 0",1ste thema
    1ste thema -> JSONTemplater [THEME]
Note: JSON body voor het API request
JSONTemplater
    CONSECUTIVE_GROUPS = Yes
    GROUP_BY = ngr_metadata_id
    GROUP_QUERY_EXPR = fme:get-attribute("group")
    RESOURCES_QUERY_EXPR:
      {
        "name":fme:get-attribute("res_name"),
        "format":fme:get-attribute("res_format"),
        "description":fme:get-attribute("res_description"),
        "url":fme:get-attribute("res_url"),
        "created":fme:get-attribute("res_created"),
        "last_modified":fme:get-attribute("res_created")
      }
    RESULT_ATTRIBUTE = data
    ROOT_QUERY_EXPR:
      {
          "name":fme:get-attribute("name"),
          "title":fme:get-attribute("title"),
          "notes":fme:get-attribute("notes"),
          "license_id":fme:get-attribute("license_id"),
          "owner_org":"provincie-zuid-holland",
          "publisher_uri":"Zuid-Holland (provincie)",
          "extras":[{"key":"NGR metadata id", "value":fme:get-attribute("ngr_metadata_id")},
                    {"key":"data.overheid.nl package id", "value":fme:get-attribute("donl_package_id")}],
          "resources":[fme:process-features("RESOURCES")],
          "tags":[fme:process-features("TAGS")],
          "theme":fme:process-features("THEME"),
          "groups":[fme:process-features("GROUP")]
      }
    TAGS_QUERY_EXPR:
      {
        "name":fme:get-attribute("tags_name")
      }
    THEME_QUERY_EXPR = fme:get-attribute("theme")
    VISIBLE_QUERY_VALIDATE = Yes
    -> HTTPCaller_2
Note: API request voor aanmaken package
HTTPCaller_2
    CONNECTION_TIMEOUT_LENGTH = 60
    CUSTOM_HEADERS = Authorization;$(api_key)
    ERROR_ATTR = _error
    FOLLOW_REDIRECTS = Yes
    HTTP_METHOD = POST
    RESPONSE_HEADER_LIST_ATTR = _headers
    SAVE_FILE = Attribute
    STATUS_CODE_ATTR = _http_status_code
    TARGET_ATTR = _response_body
    TARGET_ATTR_ENCODING = auto-detect
    TARGET_URL = $(dataplatform_url)/api/3/action/package_create
    TRANSFER_TIMEOUT_LENGTH = 90
    UPLOAD_BODY = @Value(data)
    UPLOAD_CONTENT_TYPE = JSON (application/json)
    UPLOAD_TYPE = Specify Upload Body
    USE_COOKIES = No
    VERIFY_SSL_CERTIFICATES = No
